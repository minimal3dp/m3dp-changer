# HISTORICAL 30 mm dock — not for the active raised-rail build.
"""Native editable two-station 6.11 dock and exterior-2020 fit coupon.

A pair occupies 68 mm: 30 mm within a pair, 38 mm across a pair boundary.
The exterior saddle avoids assuming a 5/6 mm T-slot. Select T-nuts for the
actual purchased profile and establish screw length with the fit coupon.
"""
from pathlib import Path
import hashlib
import json
import math
import re
import traceback
import FreeCAD as App
import FreeCADGui as Gui
import Part
import MeshPart

OUT = Path(__file__).resolve().parent
LOG = OUT / "two-station-dock-macro.log"
LOG.write_text("Started\n")
SOURCE = next((p for p in [OUT / 'source' / 'dock-6.11-EN.STEP', OUT.parent / 'dock-6.11-EN.STEP', OUT.parents[2] / 'dock-6.11-EN.STEP'] if p.is_file()), None)


def box(doc, name, x, y, z, length, width, height):
    o = doc.addObject('Part::Box', name)
    o.Length, o.Width, o.Height = length, width, height
    o.Placement.Base = App.Vector(x, y, z)
    return o


def cylinder(doc, name, x, y, z, radius, height):
    o = doc.addObject('Part::Cylinder', name)
    o.Radius, o.Height = radius, height
    o.Placement.Base = App.Vector(x, y, z)
    return o


def cut(doc, name, base, tool):
    o = doc.addObject('Part::Cut', name)
    o.Base, o.Tool, o.Refine = base, tool, True
    return o


def fuse(doc, name, parts):
    o = doc.addObject('Part::MultiFuse', name)
    o.Shapes, o.Refine = parts, True
    return o


def parameters(obj):
    for name, value, explanation in [
        ('RailWidth', 20.0, 'Nominal exterior profile width; no internal slot geometry is assumed.'),
        ('SideClearance', 0.15, 'Trial clearance per side. Test and edit using the rail coupon.'),
        ('StandOff', 5.0, 'Air space under original latch ports and above the profile top.'),
        ('LipWall', 2.0, 'Thickness of each exterior rail registration lip.'),
        ('LipDepth', 4.0, 'Engagement down the outside of the extrusion.'),
        ('ClampBore', 3.4, 'Printed M3 clearance hole; verify actual print fit.'),
        ('HeadSeatDiameter', 5.8, 'Trial M3 cap-head clearance; verify with the rail coupon before enlarging further.'),
    ]:
        obj.addProperty('App::PropertyLength', name, 'Rail fit', explanation)
        setattr(obj, name, value)
    obj.setEditorMode('RailWidth', 1)


def feet_and_lips(doc, params, x, length):
    p = params.Name
    front = box(doc, 'FrontBearingFoot', x, -2.15, -5, length, 7.15, 5)
    front.setExpression('Width', '5 mm + '+p+'.SideClearance + '+p+'.LipWall')
    front.setExpression('Height', p+'.StandOff')
    front.setExpression('Placement.Base.y', '-'+p+'.SideClearance - '+p+'.LipWall')
    front.setExpression('Placement.Base.z', '-'+p+'.StandOff')
    back = box(doc, 'RearBearingFoot', x, 15, -5, length, 7.15, 5)
    back.setExpression('Width', '5 mm + '+p+'.SideClearance + '+p+'.LipWall')
    back.setExpression('Height', p+'.StandOff')
    back.setExpression('Placement.Base.y', p+'.RailWidth - 5 mm')
    back.setExpression('Placement.Base.z', '-'+p+'.StandOff')
    lip_front = box(doc, 'FrontExteriorRegister', x, -2.15, -9, length, 2, 4)
    lip_front.setExpression('Width', p+'.LipWall')
    lip_front.setExpression('Height', p+'.LipDepth')
    lip_front.setExpression('Placement.Base.y', '-'+p+'.SideClearance - '+p+'.LipWall')
    lip_front.setExpression('Placement.Base.z', '-'+p+'.StandOff - '+p+'.LipDepth')
    lip_back = box(doc, 'RearExteriorRegister', x, 20.15, -9, length, 2, 4)
    lip_back.setExpression('Width', p+'.LipWall')
    lip_back.setExpression('Height', p+'.LipDepth')
    lip_back.setExpression('Placement.Base.y', p+'.RailWidth + '+p+'.SideClearance')
    lip_back.setExpression('Placement.Base.z', '-'+p+'.StandOff - '+p+'.LipDepth')
    return [front, back, lip_front, lip_back]


def clamp_hole(doc, params, shape, x, name):
    bore = cylinder(doc, name+'M3Clearance', x, 10, -0.1, 1.7, 6.2)
    bore.setExpression('Radius', params.Name+'.ClampBore / 2')
    shape = cut(doc, name+'ClearanceCut', shape, bore)
    # Add 0.15 mm radial cap-head clearance to the original seat. The upper
    # pocket is already open toward the latch; its lower ledges stay intact.
    head = cylinder(doc, name+'HeadSeat', x, 10, 3, 2.9, 3.1)
    head.setExpression('Radius', params.Name+'.HeadSeatDiameter / 2')
    return cut(doc, name+'HeadSeatCut', shape, head)


def bounds(s):
    b = s.BoundBox
    return [b.XMin,b.YMin,b.ZMin,b.XMax,b.YMax,b.ZMax]


def delta(a,b):
    return a.cut(b).Volume + b.cut(a).Volume


def one_solid(s):
    assert s.isValid() and len(s.Solids)==1 and s.Solids[0].isClosed()


def finish(doc, final, basename):
    doc.recompute()
    one_solid(final.Shape)
    assert not any('Error' in o.State or 'Invalid' in o.State for o in doc.Objects)
    for obj in doc.Objects:
        if hasattr(obj, 'Visibility'): obj.Visibility = obj == final
    final.ViewObject.ShapeColor=(0.20,0.57,0.72)
    Gui.activeDocument().activeView().viewAxonometric()
    Gui.activeDocument().activeView().fitAll()
    # The text camera API also works when Pivy/SWIG is not loaded.
    view = Gui.activeDocument().activeView()
    camera = view.getCamera()
    camera = re.sub(r'(\bheight\s+)([0-9.eE+-]+)',
                    lambda m: m.group(1) + str(float(m.group(2)) * 1.25), camera)
    view.setCamera(camera)
    doc.saveAs(str(OUT/(basename+'.FCStd')))
    Part.export([final],str(OUT/(basename+'.step')))
    reimport=Part.read(str(OUT/(basename+'.step')))
    one_solid(reimport)
    step_delta=delta(final.Shape,reimport)
    assert step_delta < 0.0001
    exact_bounds=bounds(final.Shape)
    mesh=MeshPart.meshFromShape(Shape=final.Shape,LinearDeflection=0.04,AngularDeflection=math.radians(8),Relative=False)
    mesh.write(str(OUT/(basename+'.stl')))
    Gui.activeDocument().activeView().saveImage(str(OUT/(basename+'-preview.png')),1400,900,'White')
    doc.save()
    return {'valid':True,'closed':True,'solids':1,'volume_mm3':final.Shape.Volume,
            'bounds_mm':exact_bounds,'step_roundtrip_difference_mm3':step_delta,
            'stl_facets':mesh.CountFacets,'native_saved':True,
            'native_reopen_validation':'Run verify-modular-documents.FCMacro separately after generation.'}


try:
    assert SOURCE is not None, 'Source dock-6.11-EN.STEP was not found'
    original=Part.read(str(SOURCE))
    one_solid(original)
    doc=App.newDocument('CxTwoStationDock')
    doc.Label='CxChanger 6.11 - repeatable two-station dock'
    doc.Comment='68 mm module; 30 mm internal pitch, 38 mm boundary pitch. 2020 exterior saddle with trial 0.15 mm side clearance and 5 mm hook-head space. Mechanical prototype; verify fit/load/clearance and add cooling integration.'
    source=doc.addObject('Part::Feature','Source611Dock')
    source.Shape=original
    parameters(source)
    source.addProperty('App::PropertyString','SourceSHA256','Provenance')
    source.SourceSHA256=hashlib.sha256(SOURCE.read_bytes()).hexdigest()
    source.setEditorMode('SourceSHA256',1)
    clipping=box(doc,'TwoStationClip',30,-60,-1,60,100,30)
    core=doc.addObject('Part::Common','OriginalTwoStationInterfaces')
    core.Base,core.Tool,core.Refine=source,clipping,True
    # Full left margin encloses the original frame clamp. Right margin and
    # small fill remove only the unused third-frame-hole crescent, beyond
    # the selected station's final latch pocket (which ends at X87.25).
    leftcap=box(doc,'LeftClampMargin',26,0,0,4,20,6)
    rightcap=box(doc,'RightEndMargin',90,0,0,4,20,6)
    unused=box(doc,'UnusedRightFramePocketFill',88.9,7.1,0,1.1,5.8,6)
    blank=fuse(doc,'SupportedModuleBlank',[core,leftcap,rightcap,unused,*feet_and_lips(doc,source,26,68)])
    shape=blank
    for name,x in [('LeftClamp',31.7),('RightClamp',61.7)]:
        shape=clamp_hole(doc,source,shape,x,name)
    # Keep the exact rear pin seat and its fastener accessible from underneath.
    # These cuts stop at Z0; no original pin-seat material above Z0 is removed.
    for name,x in [('FirstPinAccess',37),('SecondPinAccess',67)]:
        tool=cylinder(doc,name,x,22.75,-9.1,4,9.1)
        tool.setExpression('Height',source.Name+'.StandOff + '+source.Name+'.LipDepth + 0.1 mm')
        tool.setExpression('Placement.Base.z','-'+source.Name+'.StandOff - '+source.Name+'.LipDepth - 0.1 mm')
        shape=cut(doc,name+'Cut',shape,tool)
    final=shape
    final.Label='PRINT x N - two-station module, 68 mm repeat'
    doc.recompute()
    one_solid(final.Shape)
    # Exempt only the intentionally revised frame-clamp holes and unused
    # right-edge frame pocket. Every latch, pin seat and nozzle pad is exact.
    protected=Part.makeBox(60,100,30,App.Vector(30,-60,0))
    for x in (31.7,61.7):
        protected=protected.cut(Part.makeCylinder(2.9,6.1,App.Vector(x,10,0)))
    protected=protected.cut(Part.makeBox(1.1,5.8,6.1,App.Vector(88.9,7.1,0)))
    preservation=delta(final.Shape.common(protected),original.common(protected))
    assert preservation<0.0001, 'Pickup/pin/pad interfaces changed'
    latch_differences=[]
    for x in (34.7,49.7,64.7,79.7):
        region=Part.makeBox(7.55,6.4,6.1,App.Vector(x,6.8,0))
        latch_differences.append(delta(final.Shape.common(region),original.common(region)))
    assert max(latch_differences)<0.0001, 'A latch-port interface changed'
    # Treat the entire unknown 20x20 profile as solid, a conservative exterior
    # fit envelope. Its T-slot/bolts are not modeled or claimed compatible.
    rail=Part.makeBox(72,20,20,App.Vector(24,0,-25))
    rail_collision=final.Shape.common(rail).Volume
    assert rail_collision<0.0001
    # All latch ports lie in this Y band. A 3 mm M3 cap head may occupy the
    # 3 mm directly beneath the original underside, leaving 2 mm to the rail.
    hooks=Part.makeBox(60,6.4,3,App.Vector(30,6.8,-3))
    hook_collision=final.Shape.common(hooks).Volume
    assert hook_collision<0.0001
    neighbor=final.Shape.copy();neighbor.translate(App.Vector(68,0,0))
    neighbor_collision=final.Shape.common(neighbor).Volume
    assert neighbor_collision<0.0001
    module_report=finish(doc,final,'two-station-dock')
    module_report.update({'module_width_mm':68,'stations_per_module':2,
        'pad_centers_x_mm':[48,78],'internal_pitch_mm':30,'boundary_pitch_mm':38,
        'rail_exterior_mm':20,'rail_side_clearance_mm':0.15,'stand_off_mm':5,
        'nominal_hook_head_height_mm':3,'head_to_rail_clearance_mm':2,
        'protected_interface_difference_mm3':preservation,
        'latch_port_region_differences_mm3':latch_differences,
        'left_end_headseat_wall_mm':2.8,'preceding_latch_web_mm':1.55,
        'rail_envelope_collision_mm3':rail_collision,'hook_head_envelope_collision_mm3':hook_collision,
        'adjacent_module_collision_mm3':neighbor_collision,
        'clamp_holes_xy_mm':[[31.7,10],[61.7,10]],'clamp_clearance_diameter_mm':3.4,
        'head_seat_diameter_mm':5.8,'head_seat_depth_mm':3,
        'pin_access_centers_xy_mm':[[37,22.75],[67,22.75]],'pin_access_diameter_mm':8,
        'source_sha256':source.SourceSHA256})
    # Small, independently editable coupon reproduces rail bearing, exterior
    # registration and the complete original clamp stack (6 mm plate + gap).
    coupon=App.newDocument('Cx2020RailFitCoupon')
    coupon.Label='2020 rail fit coupon - trial 20.3 mm saddle'
    plate=box(coupon,'CouponPlate',0,0,0,18,20,6)
    parameters(plate)
    base=fuse(coupon,'CouponSaddle',[plate,*feet_and_lips(coupon,plate,0,18)])
    cfinal=clamp_hole(coupon,plate,base,9,'CouponClamp')
    cfinal.Label='PRINT FIRST - rail exterior and M3 clamp fit'
    coupon.recompute()
    coupon_report=finish(coupon,cfinal,'2020-rail-fit-coupon')
    coupon_report.update({'rail_exterior_mm':20,'rail_side_clearance_mm':0.15,
        'stand_off_mm':5,'plate_thickness_mm':6,'clamp_clearance_diameter_mm':3.4,
        'head_seat_diameter_mm':5.8,'head_seat_depth_mm':3})
    (OUT/'two-station-dock-freecad-validation.json').write_text(json.dumps(module_report,indent=2))
    (OUT/'2020-rail-fit-coupon-freecad-validation.json').write_text(json.dumps(coupon_report,indent=2))
except BaseException:
    LOG.write_text(traceback.format_exc())
    raise
else:
    LOG.write_text('Completed successfully\n')
    App.Console.PrintMessage('Two-station dock and 2020 rail coupon saved in '+str(OUT)+'\n')
